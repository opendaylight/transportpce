module pathdescription-stub {
  yang-version 1;
  namespace "pathdescription-stub";
  prefix pathdescription-stub;

  import transportpce-pathDescription {
    prefix transportpce-pathDescription;
    revision-date 2021-07-05;
  }

  description
    "YANG model for providing path-description through data container
    for testing purpose";

  revision 2020-12-11 {
    description
        "first version";
    reference
        "YANG model for providing path-description through data container
        for testing purpose";
  }

  container path-description {
    uses transportpce-pathDescription:path-description;
  }
}
