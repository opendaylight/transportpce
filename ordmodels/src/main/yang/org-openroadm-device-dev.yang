module org-openroadm-device-dev {
  namespace "http://org/openroadm/device-dev";
  prefix "org-openroadm-device-dev";
  import org-openroadm-device {
    prefix oroadm-device;
  }
  import ietf-yang-types {
    prefix ietf-yang-types;
  }                 

  deviation /oroadm-device:org-openroadm-device/oroadm-device:info/oroadm-device:current-datetime {
    deviate replace {               
      type ietf-yang-types:date-and-time; 
    }
  }
  deviation /oroadm-device:set-current-datetime/oroadm-device:input/oroadm-device:current-datetime {
    deviate replace {               
      type ietf-yang-types:date-and-time; 
    }
  }        
}
