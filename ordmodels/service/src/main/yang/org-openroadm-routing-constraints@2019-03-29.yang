module org-openroadm-routing-constraints {
  namespace "http://org/openroadm/routing/constrains";
  prefix org-openroadm-routing-constraints;

  import org-openroadm-common-node-types {
    prefix org-openroadm-common-node-types;
    revision-date 2018-11-30;
  }
  import org-openroadm-network-resource {
    prefix org-openroadm-network-resource;
    revision-date 2018-11-30;
  }

  organization
    "Open ROADM MSA";
  contact
    "OpenROADM.org";
  description
    "YANG definitions of routing constraints.

      Copyright of the Members of the Open ROADM MSA Agreement dated (c) 2016,
      All other rights reserved.

      Redistribution and use in source and binary forms, with or without modification,
      are permitted provided that the following conditions are met:

      * Redistributions of source code must retain the above copyright notice, this
        list of conditions and the following disclaimer.
      * Redistributions in binary form must reproduce the above copyright notice,
        this list of conditions and the following disclaimer in the documentation and/or
        other materials provided with the distribution.
      * Neither the Members of the Open ROADM MSA Agreement nor the names of its
        contributors may be used to endorse or promote products derived from this software
        without specific prior written permission.

      THIS SOFTWARE IS PROVIDED BY THE MEMBERS OF THE OPEN ROADM MSA  AGREEMENT ''AS IS''
      AND ANY EXPRESS OR IMPLIED WARRANTIES, INCLUDING, BUT NOT LIMITED TO, THE IMPLIED
      WARRANTIES OF MERCHANTABILITY AND FITNESS FOR A PARTICULAR PURPOSE ARE DISCLAIMED.
      IN NO EVENT THE MEMBERS OF THE OPEN ROADM MSA  AGREEMENT BE LIABLE FOR ANY DIRECT,
      INDIRECT, INCIDENTAL, SPECIAL, EXEMPLARY, OR CONSEQUENTIAL DAMAGES (INCLUDING, BUT
      NOT LIMITED TO, PROCUREMENT OF SUBSTITUTE GOODS OR SERVICES;  LOSS OF USE, DATA,
      OR PROFITS; OR BUSINESS INTERRUPTION) HOWEVER CAUSED AND ON ANY THEORY OF LIABILITY,
      WHETHER IN CONTRACT, STRICT LIABILITY, OR TORT (INCLUDING NEGLIGENCE OR OTHERWISE)
      ARISING IN ANY WAY OUT OF THE USE OF THIS SOFTWARE, EVEN IF ADVISED OF THE
      POSSIBILITY OF SUCH DAMAGE";

  revision 2019-03-29 {
    description
      "Version 5.0.0";
  }
  revision 2018-11-30 {
    description
      "Version 4.1.0";
  }
  revision 2018-09-28 {
    description
      "Version 4.0.0";
  }
  revision 2018-03-30 {
    description
      "Version 3.0.0";
  }
  revision 2017-12-15 {
    description
      "Version 2.2";
  }
  revision 2017-09-29 {
    description
      "Version 2.1";
  }
  revision 2017-06-26 {
    description
      "Version 2.0";
  }
  revision 2016-10-14 {
    description
      "Version 1.2";
  }

  grouping routing-constraints {
    container hard-constraints {
      uses constraints;
    }
    container soft-constraints {
      uses constraints;
    }
  }

  grouping constraints {
    leaf-list customer-code {
      type string;
    }
    choice co-routing-or-general {
      case general {
        container diversity {
          uses diversity-existing-service-constraints;
        }
        container exclude {
          uses common-constraints;
          leaf-list supporting-service-name {
            type string;
            description
              "Supporting service(s) to exclude from this route.";
          }
        }
        container include {
          uses common-constraints;
          leaf-list supporting-service-name {
            type string;
            description
              "Supporting service(s) to include in this route.";
          }
        }
        container latency {
          description
            "Maximum latency allowed";
          leaf max-latency {
            type uint32;
            units "ms";
          }
        }
    container hop-count {
          description
            "Maximum hops allowed";
          leaf max-wdm-hop-count {
            type uint8;
          }
      leaf max-otn-hop-count {
            type uint8;
          }
        }
    container TE-metric {
          description
            "Maximum cost allowed";
          leaf max-wdm-TE-metric {
            type uint32;
          }
          leaf max-otn-TE-metric {
            type uint32;
          }
         }
    container distance {
          description
            "Maximum distance allowed";
          leaf max-distance {
               type decimal64 {
               fraction-digits 2;
               }
         units "km";
          }
        }
      }
      case co-routing {
        container co-routing {
          leaf-list existing-service {
            type string;
            description
              "Diverse from existing services identified by facility CLFI";
          }
        }
      }
    }
  }

  grouping common-constraints {
    leaf-list fiber-bundle {
      type string;
    }
    leaf-list srlg-id {
      type uint32;
      description
        "unique identifier for SRLG";
    }
    leaf-list site {
      type string;
      description
        "site identifies the clli.
         clli from the device model; clli-network-ref + clli from the network model.";
    }
    leaf-list node-id {
      type org-openroadm-common-node-types:node-id-type;
      description
        "node-id from the device model; openroadm-network-ref + node-id from the network model.";
    }
    list link-identifier {
      key "link-network-id link-id";
      description
        "Refers to link-id(s) from the network model.
         The openroadm-topology-ref + link-id identifies the link in the network model.";
      uses org-openroadm-network-resource:network-link-name;
    }
  }

  grouping diversity-existing-service-constraints {
    leaf-list existing-service {
      type string;
      description
        "Diverse from existing services identified by facility CLFI";
    }
    container existing-service-applicability {
      leaf site {
        type boolean;
      }
      leaf node {
        type boolean;
      }
      leaf srlg {
        type boolean;
      }
      leaf link {
        type boolean;
      }
    }
  }
}
