module org-openroadm-otn-common-types {
  namespace "http://org/openroadm/otn-common-types";
  prefix org-openroadm-otn-common-types;

  organization
    "Open ROADM MSA";
  contact
    "OpenROADM.org";
  description
    "YANG definitions for common otn related type definitions.

     Copyright of the Members of the Open ROADM MSA Agreement dated (c) 2016,
     AT&T Intellectual Property.  All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.

     Also contains code components extracted from IETF Interfaces.  These code components
     are copyrighted and licensed as follows:

     Copyright (c) 2016 IETF Trust and the persons identified as the document authors.
     All rights reserved.

     This document is subject to BCP 78 and the IETF Trust’s Legal Provisions Relating
     to IETF Documents (http://trustee.ietf.org/license-info) in effect on the date of
     publication of this document. Please review these documents carefully, as they
     describe your rights and restrictions with respect to this document. Code Components
     extracted from this document must include Simplified BSD License text as described in
     Section 4.e of the Trust Legal Provisions and are provided without warranty as
     described in the Simplified BSD License.";

  revision 2017-09-29 {
    description
      "Version 2.1";
  }

  identity otu-rate-identity {
    description
      "A unique rate identification of the OTU.";
  }

  identity OTU4 {
    base otu-rate-identity;
    description
      "Identity for an OTU4";
  }

  identity OTU3 {
    base otu-rate-identity;
    description
      "Identity for an OTU3";
  }

  identity OTU2 {
    base otu-rate-identity;
    description
      "Identity for an OTU2";
  }

  identity OTU2e {
    base otu-rate-identity;
    description
      "Identity for an OTU2e";
  }

  identity OTU1 {
    base otu-rate-identity;
    description
      "Identity for an OTU1";
  }

  identity OTU0 {
    base otu-rate-identity;
    description
      "Identity for an OTU0";
  }

  identity OTUflex {
    base otu-rate-identity;
    description
      "Identity for an OTUflex";
  }

  identity odu-payload-type-identity {
    description
      "A unique payload type identification of the ODU.";
  }

  identity PT20 {
    base odu-payload-type-identity;
    description
      "Identity for an ODU Payload 20";
  }

  identity PT21 {
    base odu-payload-type-identity;
    description
      "Identity for an ODU Payload 21";
  }

  identity PT22 {
    base odu-payload-type-identity;
    description
      "Identity for an ODU Payload 22";
  }

  identity odu-rate-identity {
    description
      "A unique rate identification of the ODU.";
  }

  identity ODU4 {
    base odu-rate-identity;
    description
      "Identity for an ODU4";
  }

  identity ODU3 {
    base odu-rate-identity;
    description
      "Identity for an ODU3";
  }

  identity ODU2 {
    base odu-rate-identity;
    description
      "Identity for an ODU2";
  }

  identity ODU2e {
    base odu-rate-identity;
    description
      "Identity for an ODU2e";
  }

  identity ODU1 {
    base odu-rate-identity;
    description
      "Identity for an ODU1";
  }

  identity ODU0 {
    base odu-rate-identity;
    description
      "Identity for an ODU0";
  }

  identity ODUflex-cbr {
    base odu-rate-identity;
    description
      "Identity for an ODUflex-cbr";
  }

  identity ODUflex-gfp {
    base odu-rate-identity;
    description
      "Identity for an ODUflex-gfp";
  }

  identity odtu-type-identity {
    description
      "A unique identification for the MSI odtu type.";
  }

  identity ODTU4.ts-Allocated {
    base odtu-type-identity;
    description
      "OPU4 MSI - ODTU4.ts, OPU4 MSI TS is occupied/allocated.
       Applies to all ODTU4.x mappings";
  }

  identity ODTU01 {
    base odtu-type-identity;
    description
      "ODTU01 MSI type";
  }

  identity ODTU12 {
    base odtu-type-identity;
    description
      "ODTU12 MSI type";
  }

  identity ODTU13 {
    base odtu-type-identity;
    description
      "ODTU13 MSI type";
  }

  identity ODTU23 {
    base odtu-type-identity;
    description
      "ODTU23 MSI type";
  }

  identity ODTU2.ts {
    base odtu-type-identity;
    description
      "ODTU2.ts MSI type";
  }

  identity ODTU3.ts {
    base odtu-type-identity;
    description
      "ODTU3.ts MSI type";
  }

  identity unallocated {
    base odtu-type-identity;
    description
      "Unallocated MSI type";
  }

  identity odu-function-identity {
    description
      "A unique identification of the ODUk interface function.";
  }

  identity ODU-TTP {
    base odu-function-identity;
    description
      "ODU TTP facility facing trail termination";
  }

  identity ODU-CTP {
    base odu-function-identity;
    description
      "ODU CTP connection termination";
  }

  identity ODU-TTP-CTP {
    base odu-function-identity;
    description
      "ODU CTP mapper level connection termination with trail termination and client adaptation";
  }

}
