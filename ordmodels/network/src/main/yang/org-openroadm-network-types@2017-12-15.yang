module org-openroadm-network-types {
  namespace "http://org/openroadm/network/types";
  prefix nt;

  import ietf-yang-types {
    prefix yang;
    revision-date 2013-07-15;
  }
  import org-openroadm-common-types {
    prefix org-openroadm-common-types;
    revision-date 2017-12-15;
  }
  import org-openroadm-port-types {
    prefix org-openroadm-port-types;
    revision-date 2017-12-15;
  }

  organization
    "OPEN ROADM MSA";
  contact
    "www.OpenROADM.org.";
  description
    "Copyright of the Members of the Open ROADM MSA Agreement dated (c) 2016,
     AT&T Intellectual Property.  All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2017-12-15 {
    description
      "Version 2.2";
  }
  revision 2017-09-29 {
    description
      "Version 2.1";
  }
  revision 2017-07-28 {
    description
      "Version 2.0.1 - added revision-date to imports";
  }
  revision 2017-06-26 {
    description
      "Version 2.0";
  }

  typedef openroadm-node-type {
    type enumeration {
      enum "ROADM" {
        value 1;
      }
      enum "DEGREE" {
        value 11;
      }
      enum "SRG" {
        value 12;
      }
      enum "XPONDER" {
        value 3;
      }
      enum "EXT-PLUGGABLE" {
        value 4;
      }
      enum "TPDR" {
        value 13;
      }
      enum "MUXPDR" {
        value 14;
      }
      enum "REGEN" {
        value 15;
      }
      enum "REGEN-UNI" {
        value 16;
      }
      enum "SWITCH" {
        value 17;
      }
    }
  }

  typedef openroadm-tp-type {
    type enumeration {
      enum "DEGREE-TX-TTP" {
        value 1;
      }
      enum "DEGREE-RX-TTP" {
        value 2;
      }
      enum "DEGREE-TX-CTP" {
        value 3;
      }
      enum "DEGREE-RX-CTP" {
        value 4;
      }
      enum "SRG-TX-CP" {
        value 5;
      }
      enum "SRG-RX-CP" {
        value 6;
      }
      enum "SRG-TXRX-PP" {
        value 7;
      }
      enum "SRG-RX-PP" {
        value 8;
      }
      enum "SRG-TX-PP" {
        value 9;
      }
      enum "XPONDER-NETWORK" {
        value 10;
      }
      enum "XPONDER-CLIENT" {
        value 11;
      }
      enum "EXT-PLUGGABLE-TP" {
        value 12;
      }
      enum "DEGREE-TXRX-TTP" {
        value 13;
      }
      enum "SRG-TXRX-CP" {
        value 14;
      }
      enum "XPONDER-PORT" {
        value 15;
      }
      enum "DEGREE-TXRX-CTP" {
        value 16;
      }
    }
  }

  typedef openroadm-link-type {
    type enumeration {
      enum "EXPRESS-LINK" {
        value 1;
      }
      enum "ADD-LINK" {
        value 2;
      }
      enum "DROP-LINK" {
        value 3;
      }
      enum "ROADM-TO-ROADM" {
        value 4;
      }
      enum "XPONDER-INPUT" {
        value 5;
      }
      enum "XPONDER-OUTPUT" {
        value 6;
      }
      enum "OTN-LINK" {
        value 7;
      }
    }
  }

  typedef openroadm-node-status {
    type enumeration {
      enum "PLANNED" {
        value 1;
      }
      enum "DEPLOYED" {
        value 2;
      }
      enum "MAINTENANCE" {
        value 3;
      }
    }
  }

  grouping wavelengths {
    leaf index {
      type uint32;
    }
    uses flex-wave;
  }

  grouping flex-wave {
    leaf frequency {
      type org-openroadm-common-types:frequency-THz;
      config true;
      description
        "Center Frequency in THz";
    }
    leaf width {
      type org-openroadm-common-types:frequency-GHz;
      config true;
      description
        "Frequency width in GHz.";
    }
  }

  grouping xpdr-tp-supported-interfaces {
    list supported-interface-capability {
      key "if-cap-type";
      description
        "Supported interface capability on the port.";
      leaf if-cap-type {
        type identityref {
          base org-openroadm-port-types:supported-if-capability;
        }
        description
          "Interface type/hierarchy/rate supported on this port";
      }
    }
  }

  grouping node-due-date-list {
    list due-dates {
      key "id";
      leaf id {
        type uint16;
      }
      leaf start-date {
        type yang:date-and-time;
        description
          "date and time node will begin maintenance status or date when node is planned";
      }
      leaf end-date {
        type yang:date-and-time;
        description
          "date and time node will end maintenance or date when node is deployed";
      }
    }
  }
}
