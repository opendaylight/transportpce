module org-openroadm-opposite-links {
  namespace "http://org/openroadm/opposite/links";
  prefix opp-links;

  import ietf-network {
    prefix nd;
    revision-date 2015-06-08;
  }
  import ietf-network-topology {
    prefix nwt;
    revision-date 2015-06-08;
  }

  revision 2017-09-29 {
    description
      "Version 2.1";
  }

  augment "/nd:network/nwt:link" {
    when "../nd:network-types/openroadm-topology";
    description
      "Introduce new field opposite-links";
    leaf opposite-link {
        type leafref {
          path "../../nwt:link/nwt:link-id";
        }
        description
          "optional - pointer to reverse link in case of bidirectional link";
    }
  }
}
