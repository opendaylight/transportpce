module org-openroadm-degree {
  yang-version 1.1;
  namespace "http://org/openroadm/degree";
  prefix dgr;

  import org-openroadm-common-link-types {
    prefix org-openroadm-common-link-types;
    revision-date 2018-11-30;
  }
  import org-openroadm-network-types {
    prefix org-openroadm-network-types;
    revision-date 2018-11-30;
  }

  organization
    "Open ROADM MSA";
  contact
    "OpenROADM.org.";
  description
    "YANG definitions for a Degree in Network Model


     Copyright of the Members of the Open ROADM MSA Agreement dated (c) 2016,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2018-11-30 {
    description
      "Version 4.1.0";
  }
  revision 2018-09-28 {
    description
      "Version 4.0.0";
  }
  revision 2018-05-30 {
    description
      "Version 3.1.0";
  }
  revision 2018-03-30 {
    description
      "Version 3.0.0";
  }
  revision 2017-12-15 {
    description
      "Version 2.2";
  }
  revision 2017-09-29 {
    description
      "Version 2.1";
  }
  revision 2017-07-28 {
    description
      "Version 2.0.1 - added revision-date to imports";
  }
  revision 2017-06-26 {
    description
      "Version 2.0";
  }
  revision 2016-10-14 {
    description
      "Version 1.2";
  }

  grouping degree-used-wavelengths {
    description
      "This list is created to accommodate fixed grid (1.2.1) as well as flex grid (2.0 above). In case of fixed grid
       index number will refer to one of the 96 WL defined in the wavelength map file. In case of flex grid this
       will hold list of used spectra";
    list used-wavelengths {
      key "index";
      uses org-openroadm-network-types:wavelengths;
    }
  }

  grouping degree-node-attributes {
    description
      "Defines the group of degree attributes";
    leaf degree-number {
      type uint16;
    }
    leaf max-wavelengths {
      type uint32;
      description
        "maximum # of wavelengths";
    }
    list available-wavelengths {
      key "index";
      description
        "This list is created to accommodate fixed grid (1.2.1) as well as flex grid (2.0 above). In case of fixed grid
         index number will refer to one of the 96 WL defined in the wavelength map file. In case of flex grid this
         will hold list of available spectra";
      uses org-openroadm-network-types:wavelengths;
    }
    leaf ingress-span-loss-aging-margin {
      type org-openroadm-common-link-types:ratio-dB;
      config true;
      description
        "Span-loss margin extracted from corresponding device OTS interface container, optional";
    }
    leaf eol-max-load-pIn {
      type org-openroadm-common-link-types:power-dBm;
      config true;
      description
        "End Of Life Total input power at maximum load extracted from corresponding device OTS interface container";
    }
  }
}
