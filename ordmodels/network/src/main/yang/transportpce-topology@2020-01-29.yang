module transportpce-topology {
    yang-version 1.1;
    namespace "http://transportpce/topology";
    prefix "transportpce-topology";

    import ietf-network {
        prefix nd;
        revision-date 2018-02-26;
      }
    import ietf-network-topology {
        prefix nwt;
        revision-date 2018-02-26;
      }
    import org-openroadm-common-network {
        prefix cnet;
        revision-date 2018-11-30;
      }

    organization
        "TransportPCE team";
    contact
        "TransportPCE team";

    revision 2020-01-29 {
        description "Add transportpce augmentation to manage otn-link-type in otn-topology";
    }
    revision 2020-01-23 {
        description "Add transportpce augmentation for otn-topology";
    }
    revision 2019-06-25 {
        description "Initial revision";
    }

    typedef otn-link-type {
      type enumeration {
        enum "OTU4" {
          value 0;
        }
        enum "ODU4" {
          value 1;
        }
        enum "ODTU4" {
          value 2;
        }
        enum "ODU2e" {
          value 3;
        }
        enum "ODU0" {
          value 4;
        }
      }
    }

    augment "/nd:networks/nd:network/nd:node/nwt:termination-point" {
        when "../../nd:network-types/cnet:openroadm-common-network/openroadm-topology or ../../nd:network-types/cnet:openroadm-common-network/otn-topology";
        description
          "Defines associated logical-connection-point for XPDR port.";
        leaf associated-connection-map-port {
          when
            "../cnet:tp-type = 'XPONDER-CLIENT' or ../cnet:tp-type = 'XPONDER-NETWORK'";
          type string;
          description
            "The xpdr port connectable regarding the device connection-map";
        }
    }

    augment "/nd:networks/nd:network/nwt:link" {
        when "../nd:network-types/cnet:openroadm-common-network/otn-topology";
        description
          "Defines more accurate otn link types to differentiate otn links in otn-topology";
        leaf otn-link-type {
          when
            "../cnet:link-type = 'OTN-LINK'";
          type otn-link-type;
          description
              "type of otn link, to help link management inside transportpce";
          }
    }
}
