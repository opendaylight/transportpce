module org-openroadm-common-network {
  yang-version 1.1;
  namespace "http://org/openroadm/common/network";
  prefix cnet;

  import ietf-network {
    prefix nd;
    revision-date 2018-02-26;
  }
  import ietf-network-topology {
    prefix nwt;
    revision-date 2018-02-26;
  }
  import org-openroadm-network-types {
    prefix org-openroadm-network-types;
    revision-date 2018-11-30;
  }
  import org-openroadm-common-state-types {
    prefix org-openroadm-common-state-types;
    revision-date 2018-11-30;
  }
  import org-openroadm-equipment-states-types {
    prefix org-openroadm-equipment-states-types;
    revision-date 2018-11-30;
  }

  organization
    "OPEN ROADM MSA";
  contact
    "www.OpenROADM.org.";
  description
    "Copyright of the Members of the Open ROADM MSA Agreement dated (c) 2016,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2018-11-30 {
    description
      "Version 4.1.0";
  }
  revision 2018-09-28 {
    description
      "Version 4.0.0";
  }
  revision 2018-05-30 {
    description
      "Version 3.1.0";
  }
  revision 2018-03-30 {
    description
      "Version 3.0.0";
  }

  augment "/nd:networks/nd:network/nd:network-types" {
    description
      "Introduce new network type for the Open ROADM common network";
    container openroadm-common-network {
      presence "indicates common network of Open ROADMs";
      description
        "The presence of the container node indicates Open ROADM common network";
    }
  }
  augment "/nd:networks/nd:network/nd:node" {
    when "../nd:network-types/openroadm-common-network";
    description
      "Augment the generic network node with Open ROADM common attributes.";
    leaf node-type {
      type org-openroadm-network-types:openroadm-node-type;
      description
        "A component of the network topology. Once the node-type is configured, it should not be modified.";
    }
    leaf node-status {
      type org-openroadm-network-types:openroadm-node-status;
      status deprecated;
    }
    leaf lifecycle-state {
      type org-openroadm-common-state-types:lifecycle-state;
      description
        "Lifecycle State of a node. Whether it is planned, deployed, in maintenance, etc.";
    }
    leaf operational-state {
      type org-openroadm-common-state-types:state;
    }
    leaf administrative-state {
      type org-openroadm-equipment-states-types:admin-states;
    }
  }
  augment "/nd:networks/nd:network/nd:node/nwt:termination-point" {
    when "../../nd:network-types/openroadm-common-network";
    leaf tp-type {
      type org-openroadm-network-types:openroadm-tp-type;
      description
        "The type of a termination point in the ROADM topology.";
    }
    leaf eqpt-srg-id {
      type uint32;
      description
        "Shared Risk Group identifier. All ports in a circuit-pack will have same srg-id";
    }
    leaf lifecycle-state {
      type org-openroadm-common-state-types:lifecycle-state;
      description
        "Lifecycle State of a termination point. Whether it is planned, deployed, in maintenance, etc.";
    }
    leaf operational-state {
      type org-openroadm-common-state-types:state;
    }
    leaf administrative-state {
      type org-openroadm-equipment-states-types:admin-states;
    }
  }
  augment "/nd:networks/nd:network/nwt:link" {
    when "../nd:network-types/openroadm-common-network";
    description
      "This augmentation defines common link attributes in the Open ROADM common network";
    leaf link-type {
      type org-openroadm-network-types:openroadm-link-type;
    }
    leaf clfi {
      type string;
    }
    leaf opposite-link {
      type leafref {
        path "../../nwt:link/nwt:link-id";
      }
      description
        "optional - pointer to reverse link in case of bidirectional link. Supersedes opposite-link
         originally defined in OMS-attributes container, to apply to any kind of link in the topology";
    }
    leaf link-length {
      type decimal64 {
        fraction-digits 2;
      }
    }
    leaf link-latency {
      type uint32;
      description
        "Latency of a link";
    }
    leaf TE-metric {
      type uint32;
      description
        "defines a Traffic Engineering metric which could be used for any type of link.
         Supersedes TE-metric originally defined in OMS-attributes grouping";
    }
    list link-concatenation {
      key "SRLG-Id";
      leaf SRLG-Id {
        type uint32;
        description
          "unique identifier for SRLG";
      }
      leaf SRLG-length {
        type uint32;
        description
          "fiber length in meters";
      }
    }
    leaf administrative-group {
      type uint32;
      description
        "according to RFC 3630 definition";
    }
    leaf operational-state {
      type org-openroadm-common-state-types:state;
    }
    leaf administrative-state {
      type org-openroadm-equipment-states-types:admin-states;
    }
    leaf lifecycle-state {
      type org-openroadm-common-state-types:lifecycle-state;
      description
        "Lifecycle State of a link. Whether it is planned, deployed, in maintenance, etc.";
    }
  }
}
