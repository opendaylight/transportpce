module org-openroadm-physical-types {
  namespace "http://org/openroadm/physical/types";
  prefix org-openroadm-physical-types;

  import org-openroadm-common-types {
    prefix org-openroadm-common-types;
    revision-date 2017-12-15;
  }
  import ietf-yang-types {
    prefix yang;
    revision-date 2013-07-15;
  }

  organization
    "Open ROADM MSA";
  contact
    "OpenROADM.org";
  description
    "YANG definitions of physical types.

     Copyright of the Members of the Open ROADM MSA Agreement dated (c) 2016,
     AT&T Intellectual Property.  All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2017-12-15 {
    description
      "Version 2.2";
  }
  revision 2017-09-29 {
    description
      "Version 2.1";
  }
  revision 2017-07-28 {
    description
      "Version 2.0.1 - added revision-date to imports";
  }
  revision 2017-06-26 {
    description
      "Version 2.0";
  }
  revision 2016-10-14 {
    description
      "Version 1.2";
  }

  grouping node-info {
    description
      "Physical inventory data used by the node";
    leaf vendor {
      type string;
      config false;
      mandatory true;
      description
        "Vendor of the equipment";
    }
    leaf model {
      type string;
      config false;
      mandatory true;
      description
        "Physical resource model information.";
    }
    leaf serial-id {
      type string;
      config false;
      mandatory true;
      description
        "Product Code for this physical resource";
    }
  }

  grouping common-info {
    description
      "Physical inventory data used by all other entities";
    uses node-info;
    leaf type {
      type string;
      config false;
      description
        "The specific type of this physical resource - ie the type of
         shelf, type of circuit-pack, etc.";
    }
    leaf product-code {
      type string;
      config false;
      description
        "Product Code for this physical resource";
    }
    leaf manufacture-date {
      type yang:date-and-time;
      config false;
      description
        "Manufacture date of physical resource";
    }
    leaf clei {
      type string;
      config false;
      description
        "CLEI for this physical resource";
    }
    leaf hardware-version {
      type string;
      config false;
      description
        "The version of the hardware.";
    }
    leaf operational-state {
      type org-openroadm-common-types:state;
      config false;
      description
        "Operational state of the physical resource";
    }
  }
}
