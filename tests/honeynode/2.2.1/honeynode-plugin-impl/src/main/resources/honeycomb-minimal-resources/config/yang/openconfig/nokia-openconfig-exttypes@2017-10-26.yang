module nokia-openconfig-exttypes {

  yang-version "1";

  namespace "http://nokia.com/yang/nokia-openconfig-exttypes";

  prefix "n-oc-exttypes";

  // import statements
  import openconfig-transport-types { prefix oc-opt-types; }

  // meta
  organization
    "Nokia";

  contact
    "Nokia Optical Networks";

  description
    "This module contains a set of type definitions that are used
    to extend the OpenConfig models for Nokia needs. It can be
    imported by modules that make use of these types.";

  revision "2017-10-26" {
    description
       "Removed TRIB_RATE_200G and TRIB_RATE_250G as it is defined in official openconfig yang modules";
  }

  revision "2017-08-02" {
    description
      "Added PROT_FC800";
  }

  revision "2017-05-19" {
    description
      "Added PROT_UNASSIGNED";
  }

  revision "2017-05-18" {
    description
      "Added PROT_100GE_LAN for proprietary 100GE mapping";
  }

  revision "2017-05-15" {
    description
      "Added TRIB_RATE_50 for OTU4Half mode";
  }

  revision "2017-04-18" {
    description
      "Added initial openconfig-transport-types extensions";
  }

  // identity statements

  identity PROT_OTU4x2 {
    base oc-opt-types:TRIBUTARY_PROTOCOL_TYPE;
    description "OTU 4x2 protocol";
  }

  identity PROT_OTU4Half {
    base oc-opt-types:TRIBUTARY_PROTOCOL_TYPE;
    description "OTU 4Half protocol";
  }

  identity PROT_OTU4Halfx5 {
    base oc-opt-types:TRIBUTARY_PROTOCOL_TYPE;
    description "OTU 4Halfx5 protocol";
  }

  identity PROT_FC800 {
    base oc-opt-types:TRIBUTARY_PROTOCOL_TYPE;
    description "FC-800 protocol";
  }

  identity PROT_100GE_LAN {
    base oc-opt-types:TRIBUTARY_PROTOCOL_TYPE;
    description "100G Ethernet LAN protocol";
  }

  identity PROT_UNASSIGNED {
    base oc-opt-types:TRIBUTARY_PROTOCOL_TYPE;
    description "No protocol specified";
  }

  identity TRIB_RATE_50G {
    base oc-opt-types:TRIBUTARY_RATE_CLASS_TYPE;
    description
      "50G tributary signal rate";
  }

}
