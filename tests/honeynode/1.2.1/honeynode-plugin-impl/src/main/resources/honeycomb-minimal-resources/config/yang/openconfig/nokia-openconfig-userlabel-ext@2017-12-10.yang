module nokia-openconfig-userlabel-ext {

  yang-version "1";

  namespace "http://nokia.com/yang/nokia-openconfig-userlabel-ext";

  prefix "n-oc-usrlbl-ext";

  // import statements
  import openconfig-platform  { prefix oc-platform; }

  // meta
  organization
    "Nokia";

  contact
    "Nokia Optical Networks";

  description
    "This module contains a set of type definitions that are used
    to extend the openconfig-platform model for Nokia needs. It can be
    imported by modules that make use of these types.";

  revision "2017-12-10" {
    description
      "Initial version";
  }

  // extension statements

  // feature statements

  // identity statements

  // typedef statements

  // grouping statements
  grouping userlabels {
    leaf name {
      type string;
        description
          "User-supplied name of the component";
     }
     leaf description {
       type string;
        description
          "User-supplied description of the component";
    }
  }

  grouping userlabels-config {
    description
       "Configuration data for Nokia userlabel extensions";

     uses userlabels;
  }

  grouping userlabels-state {
    description
       "Operational state data for Nokia userlabel extensions";

  }

  grouping userlabels-top {
    description "Top-level grouping for Nokia userlabel extensions";

    container nokia-userlabel-ext {
      description
          "Top-level container for Nokia userlabel extensions";

      container config {
        description
            "Configuration data for Nokia userlabel extensions";

          uses userlabels-config;
        }

        container state {

          config false;

          description
            "Operational state data for Nokia userlabel extensions";

          uses userlabels-config;
          uses userlabels-state;
        }
     }
  }

  // data definition statements

  // augment statements
  augment /oc-platform:components/oc-platform:component {
    description
       "Adding Nokia userlabel extensions to openconfig platform component";

     uses userlabels-top;
  }

}
