module transportpce-servicepath {
  namespace "http://org/transportpce/B-C-interface";
  prefix transportpce-servicepath;

  import ietf-yang-types {
    prefix yang;
  }
  import transportpce-routing-constraints {
    prefix transportpce-routing-constraints;
  }
  import org-openroadm-common-types {
    prefix org-openroadm-common-types;
  }
  import org-openroadm-resource-types {
    prefix org-openroadm-resource-types;
  }
  import org-openroadm-common-service-types {
    prefix org-openroadm-common-service-types;
  }
  import transportpce-common-service-path-types {
    prefix transportpce-common-service-path-types;
  }
  import transportpce-pathDescription {
      prefix transportpce-pathDescription;
  }
  import org-openroadm-topology {
    prefix org-openroadm-topology;
  }

  organization
    "transportPCE";
  contact
    "transportPCE committers - ODL";
  description
    "YANG definitions of B and C interfaces (transportPCE).
     Copyright © 2017 Orange, Inc. and others.  All rights reserved.
     @authors: Xavier  POUGNARD ( xavier.pougnard AT orange DOT com )
               Olivier RENAIS   ( oliver.renais   AT orange DOT com )";


  revision 2017-04-26 {
    description
      "Version 1.5";
  }

  rpc path-computation-request {
    input {
      leaf service-name {
        type string;
        description
          "Identifier for the service to be created in
           the ROADM network, e.g., CLFI, CLCI, etc. This is reported against the service, but may not get reflected in the service in the network.";
        mandatory true;
      }
      leaf resource-reserve {
          type boolean;
          description
              "indicates if resources (from local PCE topology) must be reserved until further notice (cancel-resource-reserve or topology update)";
          mandatory true;
      }
      uses transportpce-common-service-path-types:service-handler-header;
      container service-a-end {
        uses transportpce-common-service-path-types:service-endpoint-sp;
      }
      container service-z-end {
        uses transportpce-common-service-path-types:service-endpoint-sp;
      }
      uses transportpce-routing-constraints:routing-constraints-sp;
    }
    output {
      uses org-openroadm-common-service-types:configuration-response-common;
      uses transportpce-common-service-path-types:response-parameters-sp;
    }
  }

  rpc cancel-resource-reserve {
      input {
      leaf service-name {
        type string;
        mandatory true;
      }
      uses transportpce-common-service-path-types:service-handler-header;
      }
      output {
      uses org-openroadm-common-service-types:configuration-response-common;
      }
  }



  rpc service-implementation-request {
      input {
        leaf service-name {
        type string;
        description
          "Identifier for the service to be created in
           the ROADM network, e.g., CLFI, CLCI, etc. This is reported against the service, but may not get reflected in the service in the network.";
        mandatory true;
      }
      uses transportpce-common-service-path-types:service-handler-header;
      container service-a-end {
        uses transportpce-common-service-path-types:service-endpoint-sp;
      }
      container service-z-end {
        uses transportpce-common-service-path-types:service-endpoint-sp;
      }
      container path-description {
          uses transportpce-pathDescription:path-description;
      }
      }
      output {
        uses org-openroadm-common-service-types:configuration-response-common;
      }
  }

  rpc service-delete {
      input {
        leaf service-name {
        type string;
        description
          "Identifier for the service to be created in
           the ROADM network, e.g., CLFI, CLCI, etc. This is reported against the service, but may not get reflected in the service in the network.";
        mandatory true;
      }
      uses transportpce-common-service-path-types:service-handler-header;
      }
      output {
        uses org-openroadm-common-service-types:configuration-response-common;
      }
  }

  container service-path-list {
    description
      "List of service paths. Can only be created, deleted, modified, etc. using special RPCs.";
    list service-paths {
      key "service-path-name";
      uses transportpce-common-service-path-types:service-path;
    }
  }
notification service-path-rpc-result {
    description
      "This Notification indicates result of  service RPC";
    leaf notification-type {
      type transportpce-common-service-path-types:service-path-notification-types;
    }
    container path-description {
          uses transportpce-pathDescription:path-description;
    }
    uses transportpce-common-service-path-types:rpc-response-status-ex;
    uses org-openroadm-common-service-types:service-notification-result;
  }
notification service-rpc-result-sp {
    description
      "This Notification indicates result of  service RPC and provides the topology";
    leaf notification-type {
      type transportpce-common-service-path-types:service-path-notification-types;
    }
    container path-topology {
          uses org-openroadm-topology:topology;
    }
    uses transportpce-common-service-path-types:rpc-response-status-ex;
    uses org-openroadm-common-service-types:service-notification-result;
  }



}
