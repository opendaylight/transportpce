module olm {
  yang-version 1;
  namespace "urn:opendaylight:params:xml:ns:yang:olm";
  prefix "olm";

 organization
    "transportPCE";
  contact
    "transportPCE committers - ODL";
  description
    "YANG definitions of RPCs supported by OLM.
     Copyright © 2017 AT&T and others.  All rights reserved.
     authors: Dhruv Bhardwaj ( db929a@att.com )
              Shweta Vachhani ( sv111y@att.com )";

  revision "2017-04-18" {
    description "Initial revision of olm model";
  }
  rpc get-pm {
    input{
      leaf node-id{
        type string;
      }
      leaf resource-type{
        type string;
      }
      leaf resource-name{
        type string;
      }
      leaf granularity{
        type string;
      }
    }
    output{
      leaf node-id{
        type string;
      }
      leaf resource-type{
        type string;
      }
      leaf resource-id{
        type string;
      }
      leaf granularity {
        type string;
      }
      list measurements {
      leaf pmparameter-name{
        type string;
      }
      leaf pmparameter-value {
        type string;
        }
      }
    }
  }
  rpc service-power-setup{
    input{
      leaf wave-number{
        type uint32;
      }
      list nodes{
        ordered-by user;
        leaf node-id{
          type string;
        }
        leaf src-tp{
          type string;
          description "Source termination point ";
          mandatory true;
        }
        leaf dest-tp{
          type string;
          description "Destination termination point ";
           mandatory true;
        }
      }
    }
    output{
      leaf result{
        type string;
      }
    }
  }
  rpc service-power-turndown{
    input{
      leaf wave-number{
        type uint32;
      }
      list nodes{
        ordered-by user;
        leaf node-id{
          type string;
        }
        leaf src-tp{
          type string;
          description "Source termination point ";
          mandatory true;
        }
        leaf dest-tp{
          type string;
          description "Destination termination point ";
           mandatory true;
        }
      }
    }
    output{
      leaf result{
        type string;
      }
    }
  }
}
