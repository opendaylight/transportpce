module portmapping {
  yang-version 1;
  namespace "urn:opendaylight:params:xml:ns:yang:portmapping";
  prefix "portmapping";

  import org-openroadm-common-types {
    prefix org-openroadm-common-types;
    revision-date 2016-10-14;
  }

 organization
    "transportPCE";
  contact
    "transportPCE committers - ODL";
  description
    "YANG definitions of RPCs supported by OLM.
     Copyright (c) 2017 AT&T and others.  All rights reserved.
     authors: Dhruv Bhardwaj ( db929a@att.com )
              Shweta Vachhani ( sv111y@att.com )";

  revision "2017-02-28" {
    description "Initial revision of port mapping model";
  }
  container network{
    list nodes{
      key node-id;
      leaf node-id{
        type string;
        description
          "Unique identifier for node in the network";
      }
      leaf node-type{
        type org-openroadm-common-types:node-types;
        description
          "Identifier for node-type e.g Roadm, xponder";
      }
      list mapping{
        description
          "Mapping for Physical circuit pack/port/parent interfaces
          corresponding to each logical connection point present in the node.";
        key logical-connection-point;
        leaf logical-connection-point{
          type string;
        }
        leaf supporting-circuit-pack-name{
          type string;
          description
          "Circuit pack where the logical connection point is located";
        }
        leaf supporting-port{
          type string;
          description
          "Port where the logical connection point is located";
        }
        leaf supporting-oms{
          type string;
          description
          "OMS interface provisioned on the port";
        }
        leaf supporting-ots{
          type string;
          description
          "OTS interface provisioned on the port";
        }
      }
      list cp-to-degree{
        description
          "This mapping helps locate degree number of the circuitpack that does lldp
         protocol management";
       key circuit-pack-name;
       leaf circuit-pack-name{
          type string;
       }
       leaf degree-number{
            type uint32;
       }
       leaf interface-name{
          type string;
       }
      }
    }
  }
}
