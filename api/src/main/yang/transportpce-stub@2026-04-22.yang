module transportpce-stub {
  yang-version 1;
  namespace "http://org/opendaylight/transportpce/stub";
  prefix org-opendaylight-transportpce-stub;

  import transportpce-pathDescription {
    prefix transportpce-pathDescription;
    revision-date 2026-04-22;
  }


  organization
    "transportPCE";
  contact
    "transportPCE committers - ODL";
  description
    "YANG definitions for defining port mapping in TransportPCE.
     Copyright (c) 2023 Orange and others. All rights reserved.
     authors: Gilles Thouenon Emmanuelle Delfour";

  revision 2026-04-22 {
    description
      "Model to parse json input file for FrequenciesServiceTests";
  }

  container path-description {
      uses transportpce-pathDescription:path-description;
  }
}
