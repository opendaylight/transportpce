module gnpy-api {
  yang-version 1;
  namespace "gnpy:gnpy-api";
  prefix gnpyapi;

  import gnpy-network-topology {
    prefix gnpynt;
  }
  import gnpy-path-computation-simplified {
    prefix gnpypc;
  }

  organization
    "Telecom Infra Project OOPT PSE Working Group";
  contact
    "WG Web:   <https://github.com/Telecominfraproject/oopt-gnpy>
     contact:  <mailto:ahmed.triki@orange.com>
     contact:  <mailto:esther.lerouzic@orange.com>
    ";
  description
    "YANG model for gnpy api input for path computation - TransportPCE preversion";

  revision 2019-01-03 {
    description
      "first draft";
    reference
      "YANG model for api input for path computation with gnpy";
  }

  container gnpy-api {
    description
      "This is the structure of the body of the request to gnpy";
    container topology-file {
      description
        "Describe the topology file to connect to gnpy";
      uses gnpynt:topo;
    }
    container service-file {
      description
        "Describe the service file to connect to gnpy";
      uses gnpypc:service;
    }
  }
}
