module gnpy-api {
  yang-version 1.1;
  namespace "gnpy:gnpy-api";
  prefix gnpyapi;

  import gnpy-network-topology {
    prefix gnpynt;
  }
  import gnpy-path-computation-simplified {
    prefix gnpypc;
  }
  import gnpy-eqpt-config {
    prefix gnpyeqpt;
  }

  organization
    "Telecom Infra Project OOPT PSE Working Group";
  contact
    "WG Web:   <https://github.com/Telecominfraproject/oopt-gnpy>
     contact:  <mailto:ahmed.triki@orange.com>
     contact:  <mailto:esther.lerouzic@orange.com>
    ";
  description
    "YANG model for gnpy api input for path computation - TransportPCE preversion";

  revision 2020-10-22 {
    description
      "draft for experimental/2020-candi";
    reference
      "YANG model for api input for path computation with gnpy";
  }

  container request {
    container service {
      description
        "Describe the service file to connect to gnpy";
      uses gnpypc:service;
    }
    container topology {
      description
        "Describe the topology file to connect to gnpy";
      uses gnpynt:topo;
    }
    container equipment {
      description
        "Describe the equipment library to connect to gnpy";
      uses gnpyeqpt:eqpt;
    }
  }


}
