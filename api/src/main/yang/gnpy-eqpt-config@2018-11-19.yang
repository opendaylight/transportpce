module gnpy-eqpt-config {
  yang-version 1;
  namespace "gnpy:gnpy-eqpt-config";
  prefix gnpyeqpt;

  organization
    "Telecom Infra Project OOPT PSE
     Working Group";
  contact
    "WG Web:   <https://github.com/Telecominfraproject/oopt-gnpy>
     contact:  <mailto:ahmed.triki@orange.com>
     contact:  <mailto:esther.lerouzic@orange.com>
    ";
  description
    "Base YANG model for gnpy equipment library input for path computation - transportPCE preversion";

  revision 2018-11-19 {
    description
      "first draft";
    reference
      "Base YANG model for equipment library input for path computation with gnpy";
  }

  /*
   * Identities

  identity edfa-variety {
    description "edfa variety" ;
  }

  identity fiber-variety {
    description "base identity for fiber variety" ;
  }

  identity transceiver-variety {
    description "base identity for transceiver variety" ;
  }

   */

  list Edfa {
    key "type_variety";
    leaf type_variety {
      type string;
      description
        "a unique name to ID the amplifier in the JSON/Excel template topology input file";
    }
  }
  list Fiber {
    key "type_variety";
    description
      "a unique name to ID the fiber in the JSON or Excel template topology input file";
    leaf type_variety {
      type string;
    }
  }
  list Transceiver {
    key "type_variety";
    description
      "a unique name to ID the transceiver in the JSON or Excel template topology input file";
    leaf type_variety {
      type string;
    }
  }
  list mode {
    key "format";
    leaf format {
      type string;
      description
        "unique name of the mode";
    }
  }
  container Spans;
  container Roadms;
  container SI;
}
