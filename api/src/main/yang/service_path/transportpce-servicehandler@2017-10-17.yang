module transportpce-servicehandler {
  namespace "http://org/opendaylight/transportpce/servicehandler";
  prefix org-opendaylight-transportpce-servicehandler;

  import org-openroadm-common-service-types {
    prefix org-openroadm-common-service-types;
    revision-date 2019-05-31;
  }
  import transportpce-common-service-path-types {
    prefix transportpce-common-service-path-types;
  }

  organization
    "transportPCE";
  contact
    "transportPCE committers - ODL";
  description
    "YANG definitions of A interface (transportPCE). Adapted from service definition (openroadm)
     Copyright © 2017 Orange, Inc. and others.  All rights reserved.

     openroadm copyright:
      Copyright of the Members of the Open ROADM MSA Agreement dated (c) 2016,
      AT&T Intellectual Property.  All other rights reserved.

      Redistribution and use in source and binary forms, with or without modification,
      are permitted provided that the following conditions are met:

      * Redistributions of source code must retain the above copyright notice, this
        list of conditions and the following disclaimer.
      * Redistributions in binary form must reproduce the above copyright notice,
        this list of conditions and the following disclaimer in the documentation and/or
        other materials provided with the distribution.
      * Neither the Members of the Open ROADM MSA Agreement nor the names of its
        contributors may be used to endorse or promote products derived from this software
        without specific prior written permission.

      THIS SOFTWARE IS PROVIDED BY THE MEMBERS OF THE OPEN ROADM MSA  AGREEMENT ''AS IS''
      AND ANY EXPRESS OR IMPLIED WARRANTIES, INCLUDING, BUT NOT LIMITED TO, THE IMPLIED
      WARRANTIES OF MERCHANTABILITY AND FITNESS FOR A PARTICULAR PURPOSE ARE DISCLAIMED.
      IN NO EVENT THE MEMBERS OF THE OPEN ROADM MSA  AGREEMENT BE LIABLE FOR ANY DIRECT,
      INDIRECT, INCIDENTAL, SPECIAL, EXEMPLARY, OR CONSEQUENTIAL DAMAGES (INCLUDING, BUT
      NOT LIMITED TO, PROCUREMENT OF SUBSTITUTE GOODS OR SERVICES;  LOSS OF USE, DATA,
      OR PROFITS; OR BUSINESS INTERRUPTION) HOWEVER CAUSED AND ON ANY THEORY OF LIABILITY,
      WHETHER IN CONTRACT, STRICT LIABILITY, OR TORT (INCLUDING NEGLIGENCE OR OTHERWISE)
      ARISING IN ANY WAY OUT OF THE USE OF THIS SOFTWARE, EVEN IF ADVISED OF THE
      POSSIBILITY OF SUCH DAMAGE";

  revision 2017-10-17 {
    description
      "Version 1.6";
  }
  revision 2017-09-30 {
    description
      "Version 1.2";
  }

  notification service-rpc-result-sh {
    description
      "This Notification indicates result of service RPC";
    leaf notification-type {
      type org-openroadm-common-service-types:service-notification-types;
    }
    uses transportpce-common-service-path-types:rpc-response-status-ex;
    uses org-openroadm-common-service-types:service-notification-result;
  }
}
