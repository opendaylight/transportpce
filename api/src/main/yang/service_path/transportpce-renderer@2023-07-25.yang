module transportpce-renderer {
  namespace "http://org/opendaylight/transportpce/renderer";
  prefix org-opendaylight-transportpce-renderer;

  import org-openroadm-common-service-types {
    prefix org-openroadm-common-service-types;
  }
  import transportpce-common-service-path-types {
    prefix transportpce-common-service-path-types;
  }
  import org-openroadm-topology {
    prefix org-openroadm-topology;
  }
  import transportpce-pathDescription {
    prefix transportpce-pathDescription;
  }
  import transportpce-common-types {
      prefix org-transportpce-common-types;
    }

  organization
    "transportPCE";
  contact
    "transportPCE committers - ODL";
  description
    "YANG definitions of C interface (transportPCE). Adapted from service definition (openroadm)
     Copyright © 2017 Orange, Inc. and others.  All rights reserved.

     openroadm copyright:
      Copyright of the Members of the Open ROADM MSA Agreement dated (c) 2016,
      AT&T Intellectual Property.  All other rights reserved.

      Redistribution and use in source and binary forms, with or without modification,
      are permitted provided that the following conditions are met:

      * Redistributions of source code must retain the above copyright notice, this
        list of conditions and the following disclaimer.
      * Redistributions in binary form must reproduce the above copyright notice,
        this list of conditions and the following disclaimer in the documentation and/or
        other materials provided with the distribution.
      * Neither the Members of the Open ROADM MSA Agreement nor the names of its
        contributors may be used to endorse or promote products derived from this software
        without specific prior written permission.

      THIS SOFTWARE IS PROVIDED BY THE MEMBERS OF THE OPEN ROADM MSA  AGREEMENT ''AS IS''
      AND ANY EXPRESS OR IMPLIED WARRANTIES, INCLUDING, BUT NOT LIMITED TO, THE IMPLIED
      WARRANTIES OF MERCHANTABILITY AND FITNESS FOR A PARTICULAR PURPOSE ARE DISCLAIMED.
      IN NO EVENT THE MEMBERS OF THE OPEN ROADM MSA  AGREEMENT BE LIABLE FOR ANY DIRECT,
      INDIRECT, INCIDENTAL, SPECIAL, EXEMPLARY, OR CONSEQUENTIAL DAMAGES (INCLUDING, BUT
      NOT LIMITED TO, PROCUREMENT OF SUBSTITUTE GOODS OR SERVICES;  LOSS OF USE, DATA,
      OR PROFITS; OR BUSINESS INTERRUPTION) HOWEVER CAUSED AND ON ANY THEORY OF LIABILITY,
      WHETHER IN CONTRACT, STRICT LIABILITY, OR TORT (INCLUDING NEGLIGENCE OR OTHERWISE)
      ARISING IN ANY WAY OUT OF THE USE OF THIS SOFTWARE, EVEN IF ADVISED OF THE
      POSSIBILITY OF SUCH DAMAGE";

  revision 2023-07-25 {
        description
          "Version 1.6.5.
           Add common-Id to the service implementation request";
      }
  revision 2021-09-15 {
      description
        "Version 1.6.4.
         Add list of link-id to the notification";
    }
  revision 2021-06-18 {
      description
        "Version 1.6.3.
         Add optical-renderer-nodes to the notification";
    }
  revision 2020-11-25 {
    description
      "Version 1.6.2";
  }
  revision 2020-05-20 {
    description
      "Version 1.6.1";
  }
  revision 2017-10-17 {
    description
      "Version 1.6";
  }
  revision 2017-02-28 {
    description
      "Initial revision of renderer model version 1.5";
  }

  grouping link-for-notif {
    description
      "In most of the cases, only 2 link-termination-points exists.
       It reveals that the service is supported by a single otn-link
       to configure. Its properties can be easily transmited by this way.";
    container a-termination {
      leaf node-id {
        type string;
      }
      leaf tp-id {
        type string;
      }
    }
    container z-termination {
      leaf node-id {
        type string;
      }
      leaf tp-id {
        type string;
      }
    }
  }

  rpc service-implementation-request {
    input {
      leaf service-name {
        type string;
        mandatory true;
        description
          "Identifier for the service to be created in
           the ROADM network, e.g., CLFI, CLCI, etc. This is reported against the service, but may not get reflected in the service in the network.";
      }
      leaf common-id {
          type string;
          description
            "common-id of the service that may be associated to the considered service in temp-service-list";
      }
      leaf connection-type {
        type org-openroadm-common-service-types:connection-type;
      }
      uses transportpce-common-service-path-types:service-handler-header;
      container service-a-end {
        uses transportpce-common-service-path-types:service-endpoint-sp;
      }
      container service-z-end {
        uses transportpce-common-service-path-types:service-endpoint-sp;
      }
      container path-description {
        uses transportpce-pathDescription:path-description;
      }
    }
    output {
      uses org-openroadm-common-service-types:configuration-response-common;
    }
  }

  rpc service-delete {
    input {
      leaf service-name {
        type string;
        mandatory true;
        description
          "Identifier for the service to be created in
           the ROADM network, e.g., CLFI, CLCI, etc. This is reported against the service, but may not get reflected in the service in the network.";
      }
      uses transportpce-common-service-path-types:service-handler-header;
    }
    output {
      uses org-openroadm-common-service-types:configuration-response-common;
    }
  }

  notification renderer-rpc-result-sp {
    description
      "This Notification indicates result of renderer RPC and provides the topology";
    leaf notification-type {
      type transportpce-common-service-path-types:service-path-notification-types;
    }
    container path-topology {
      uses org-openroadm-topology:topology;
    }
    uses transportpce-pathDescription:path-description;
    uses transportpce-common-service-path-types:rpc-response-status-ex;
    uses org-openroadm-common-service-types:service-notification-result;
    container link {
      uses link-for-notif;
    }
    leaf-list link-id {
      type string;
      description
        "when more than 2 link-termination-points exists,
         it reveals that the service is supported by multiple
         links (typically, OTU4). In such a case, it is more appropriated
         to transmit the list of supported links with their link-id";
    }
    leaf service-type {
        type string;
    }
  }
}
