module tapi-networkutils {
  yang-version 1;
  namespace "http://org/opendaylight/transportpce/tapinetworkutils";
  prefix "org-opendaylight-transportpce-tapinetworkutils";

  import tapi-common {
    prefix tapi-common;
    revision-date 2018-12-10;
  }

  revision "2021-02-04" {
    description
      "Initial revision of tapi networkutils model. Used as the transportpce-networkutils model to
      create tapi links between tapi nodes in the tapi topology. The inputs are base on OR naming but later
      translated into tapi";
  }

  rpc init-roadm-roadm-link {
    description "This rpc initiates a tapi roadm to roadm link";
    input {
      leaf rdm-a-node {
        type string;
      }
      leaf deg-a-tp {
        type string;
      }
      leaf rdm-z-node {
        type string;
      }
      leaf deg-z-tp {
        type string;
      }
    }
    output {
      leaf result {
        type string;
      }
    }
  }

  rpc init-xpdr-rdm-link {
    description "This rpc initiates a tapi xponder to rdm link. Bidirectional";
    input {
      leaf xpdr-node {
        type string;
      }
      leaf network-tp {
        type string;
      }
      leaf rdm-node {
        type string;
      }
      leaf add-drop-tp {
        type string;
      }
    }
    output {
      leaf result {
        type string;
      }
    }
  }

  rpc delete-link {
    description "This rpc deletes a given link in openroadm Topology layer";
    input {
      leaf uuid {
        type tapi-common:uuid;
      }
    }
    output {
      leaf result {
        type string;
      }
    }
  }
}
